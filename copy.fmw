FME workspace copy.fmw

Parameters:
- DestDataset_CESIUM3DTILES =
- SourceDataset_CITYGML =
- SourceDataset_CITYGML_3 =
- SourceDataset_OGCGEOPACKAGE_3 =

Readers:
- CITYGML_1: CITYGML from $(SourceDataset_CITYGML)
- OGCGEOPACKAGE_1: OGCGEOPACKAGE from $(SourceDataset_OGCGEOPACKAGE_3)
- CITYGML_2: CITYGML from $(SourceDataset_CITYGML_3)

Writers:
- CESIUM3DTILES_1: CESIUM3DTILES to $(DestDataset_CESIUM3DTILES)

WallSurface (reader CITYGML_1)
    attributes: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
RoofSurface (reader CITYGML_1)
    attributes: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
GroundSurface (reader CITYGML_1)
    attributes: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
batiment (reader OGCGEOPACKAGE_1)
    attributes: ID text(24), NATURE text(34), USAGE1 text(22), USAGE2 text(22), LEGER text(3), ETAT text(15), DATE_CREAT text(19), DATE_MAJ text(19), DATE_APP date, DATE_CONF date, SOURCE text(127), ID_SOURCE text(254), ACQU_PLANI text(32), ACQU_ALTI text(30), PREC_PLANI double, PREC_ALTI double, NB_LOGTS mediumint, NB_ETAGES mediumint, MAT_MURS text(2), MAT_TOITS text(2), HAUTEUR double, Z_MIN_SOL double, Z_MIN_TOIT double, Z_MAX_TOIT double, Z_MAX_SOL double, ORIGIN_BAT text(18), APP_FF text(32), IDS_RNB text(254), fid int,PrimaryKey
    -> Reprojector
Reprojector
    DEST = EPSG:3946
    INTERPOLATION_TYPE_NAME = Nearest Neighbor
    RASTER_CELL_SIZE = Preserve Cells
    RASTER_TOLERANCE = 0.0
    REPROJECTED -> SpatialFilter [Filter]
Building (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, ADMINISTRA xml_buffer, ADRESSE xml_buffer, APPDATMAX xml_buffer, APPDATMIN xml_buffer, BUILDINGID xml_buffer, CODE_DGI xml_buffer, CODE_INSEE xml_buffer, COMIDATMAX xml_buffer, COMIDATMIN xml_buffer, CULTE xml_buffer, DEPDATMAX xml_buffer, DEPDATMIN xml_buffer, DEPLACEMEN xml_buffer, ENSEIGNEME xml_buffer, MAISDATMAX xml_buffer, MAISDATMIN xml_buffer, MILLESIME xml_buffer, NBAPP xml_buffer, NBCOMIN xml_buffer, NBDEP xml_buffer,
      NBMAIS xml_buffer, NIVAPP xml_buffer, NIVCOMIN xml_buffer, NIVDEP xml_buffer, NIVMAIS xml_buffer, NOMCOMMUNE xml_buffer, NOMOFFICIE xml_buffer, Profile xml_buffer, SANTE xml_buffer, SPORT xml_buffer, SURFTOIT xml_buffer, URGENCE xml_buffer, Volume xml_buffer, ZMAXTOIT xml_buffer, ZMINTOIT xml_buffer, ZMOYTOIT xml_buffer, insee xml_buffer, nomreduit xml_buffer
    -> 2DForcer_2
    -> FeatureJoiner [RIGHT]
2DForcer_2
    2D -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = Yes
    PASSED -> FeatureJoiner [LEFT]
FeatureJoiner
    ATTR_CONFLICT_RES = Use Left
    GEOMETRY_HANDLING = Use Right
    JOIN_KEYS = gml_id gml_id AUTO
    JOIN_MODE = Inner
    JOINED -> AppearanceRemover
    UNJOINED_RIGHT -> AppearanceRemover
AppearanceRemover
    SIDE_TO_REMOVE = Front and Back Sides
    -> Offsetter
Offsetter
    MODE = Cartesian Coordinate
    XOFF = 0
    YOFF = 0
    ZOFF = 50
    OFFSET -> output_francheville_batie (writer CESIUM3DTILES_1)
output_francheville_batie (writer CESIUM3DTILES_1)
    attributes: gml_id string, gml_parent_id string, citygml_target_uri string, citygml_feature_role string, citygml_feature_role_attr_name string, citygml_feature_role_attr_val string, gml_description string, gml_name string, citygml_creationDate string, citygml_terminationDate string, externalReference{}.externalObject.name string, externalReference{}.externalObject.uri string, externalReference{}.informationSystem string, citygml_generalizes_to{}.xlink_href string, citygml_relative_to_terrain string, citygml_relative_to_water string, citygml_appearance{}.xlink_href string, citygml_level_of_detail{} string, citygml_opening{}.xlink_href string, ID string, NATURE string, USAGE1 string, USAGE2 string, LEGER string, ETAT string, DATE_CREAT string, DATE_MAJ string, DATE_APP string, DATE_CONF string, SOURCE string,
      ID_SOURCE string, ACQU_PLANI string, ACQU_ALTI string, PREC_PLANI float, PREC_ALTI float, NB_LOGTS int, NB_ETAGES int, MAT_MURS string, MAT_TOITS string, HAUTEUR float, Z_MIN_SOL float, Z_MIN_TOIT float, Z_MAX_TOIT float, Z_MAX_SOL float, ORIGIN_BAT string, APP_FF string, IDS_RNB string, fid int, _predicate string
