FME workspace citygml_ogcgeopackage2cesium3dtiles.fmw

Parameters:
- DestDataset_CESIUM3DTILES =
- SourceDataset_CITYGML =
- SourceDataset_OGCGEOPACKAGE_3 =

Readers:
- CITYGML_1: CITYGML from $(SourceDataset_CITYGML)
- OGCGEOPACKAGE_2: OGCGEOPACKAGE from $(SourceDataset_OGCGEOPACKAGE_3)

Writers:
- CESIUM3DTILES_1: CESIUM3DTILES to $(DestDataset_CESIUM3DTILES)

RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> 2DForcer_2
    -> FeatureJoiner [RIGHT]
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> 2DForcer_2
    -> FeatureJoiner [RIGHT]
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> 2DForcer_2
    -> FeatureJoiner [RIGHT]
2DForcer_2
    2D -> SpatialFilter [Candidate]
batiment (reader OGCGEOPACKAGE_2)
    attributes: ID text(24), NATURE text(34), USAGE1 text(22), USAGE2 text(22), LEGER text(3), ETAT text(15), DATE_CREAT text(19), DATE_MAJ text(19), DATE_APP date, DATE_CONF date, SOURCE text(127), ID_SOURCE text(254), ACQU_PLANI text(32), ACQU_ALTI text(30), PREC_PLANI double, PREC_ALTI double, NB_LOGTS mediumint, NB_ETAGES mediumint, MAT_MURS text(2), MAT_TOITS text(2), HAUTEUR double, Z_MIN_SOL double, Z_MIN_TOIT double, Z_MAX_TOIT double, Z_MAX_SOL double, ORIGIN_BAT text(18), APP_FF text(32), IDS_RNB text(254), fid int,PrimaryKey
    -> Reprojector
Reprojector
    DEST = EPSG:3946
    INTERPOLATION_TYPE_NAME = Nearest Neighbor
    RASTER_CELL_SIZE = Preserve Cells
    RASTER_TOLERANCE = 0.0
    REPROJECTED -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = Yes
    PASSED -> FeatureJoiner [LEFT]
FeatureJoiner
    ATTR_CONFLICT_RES = Use Left
    GEOMETRY_HANDLING = Use Right
    JOIN_KEYS = gml_id gml_id AUTO
    JOIN_MODE = Inner
    JOINED -> AppearanceRemover
    UNJOINED_RIGHT -> AppearanceRemover
AppearanceRemover
    SIDE_TO_REMOVE = Front and Back Sides
    -> Offsetter
Offsetter
    MODE = Cartesian Coordinate
    XOFF = 0
    YOFF = 0
    ZOFF = 50
    OFFSET -> output_francheville_batie (writer CESIUM3DTILES_1)
output_francheville_batie (writer CESIUM3DTILES_1)
    attributes: gml_id string, gml_parent_id string, citygml_target_uri string, citygml_feature_role string, citygml_feature_role_attr_name string, citygml_feature_role_attr_val string, gml_description string, gml_name string, citygml_creationDate string, citygml_terminationDate string, externalReference{}.externalObject.name string, externalReference{}.externalObject.uri string, externalReference{}.informationSystem string, citygml_generalizes_to{}.xlink_href string, citygml_relative_to_terrain string, citygml_relative_to_water string, citygml_appearance{}.xlink_href string, citygml_class string, citygml_class_codeSpace string, citygml_function{} string, citygml_function{}.codeSpace string, citygml_usage{} string, citygml_usage{}.codeSpace string, citygml_year_of_construction string, citygml_year_of_demolition string, citygml_roof_type string, citygml_roof_type_codeSpace string, citygml_measured_height float, citygml_measured_height_units string, citygml_storeys_above_ground string,
      citygml_storeys_below_ground string, citygml_storey_heights_above_ground string, citygml_storey_heights_above_ground_units string, citygml_storey_heights_below_ground string, citygml_storey_heights_below_ground_units string, citygml_outer_building_installation{}.xlink_href string, citygml_interior_building_installation{}.xlink_href string, citygml_bounded_by{}.xlink_href string, citygml_level_of_detail{} string, citygml_interior_room{}.xlink_href string, citygml_consists_of_building_part{}.xlink_href string, citygml_address{}.xlink_href string, ADMINISTRA string, ADRESSE string, APPDATMAX string, APPDATMIN string, BUILDINGID string, CODE_DGI string, CODE_INSEE string, COMIDATMAX string, COMIDATMIN string, CULTE string, DEPDATMAX string, DEPDATMIN string, DEPLACEMEN string, ENSEIGNEME string, MAISDATMAX string, MAISDATMIN string, MILLESIME string, NBAPP string,
      NBCOMIN string, NBDEP string, NBMAIS string, NIVAPP string, NIVCOMIN string, NIVDEP string, NIVMAIS string, NOMCOMMUNE string, NOMOFFICIE string, Profile string, SANTE string, SPORT string, SURFTOIT string, URGENCE string, Volume string, ZMAXTOIT string, ZMINTOIT string, ZMOYTOIT string, insee string, nomreduit string
